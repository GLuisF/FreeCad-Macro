from PySide import QtGui

def askConvertToFeature(obj):
    msg = '"%s" e um objeto parametrico (%s).\nPara assar o Placement e preciso converte-lo em Part::Feature (perde parametros/historico).\nDeseja converter e continuar?' % (obj.Label, obj.TypeId)
    reply = QtGui.QMessageBox.question(None, 'Converter para Feature', msg,
                                        QtGui.QMessageBox.Yes | QtGui.QMessageBox.No)
    return reply == QtGui.QMessageBox.Yes

def freezeToStaticFeature(obj):
    # objeto parametrico (primitive, PartDesign, etc.): congela o Shape atual
    # em um Part::Feature estatico, que nao e recalculado no recompute
    doc = obj.Document
    shape = obj.Shape.copy()
    flat = doc.addObject('Part::Feature', obj.Name + '_flat')
    flat.Label = obj.Label
    flat.Shape = shape
    flat.Placement = obj.Placement
    doc.removeObject(obj.Name)
    return flat

def applyPlacementToShape(obj):
    if not hasattr(obj, "Shape") or not hasattr(obj, "Placement"):
        print('%s nao possui Shape/Placement, ignorado' % obj.Label)
        return False

    if obj.TypeId != 'Part::Feature':
        if not askConvertToFeature(obj):
            print('%s ignorado (conversao cancelada)' % obj.Label)
            return False
        obj = freezeToStaticFeature(obj)

    shape = obj.Shape.copy()
    shape.Placement = App.Placement()
    shape.transformShape(obj.Placement.toMatrix(), True)

    obj.Shape = shape
    obj.Placement = App.Placement()
    return True

sel = Gui.Selection.getSelection()
if len(sel) == 0:
    print('Nada foi selecionado')
else:
    count = 0
    for obj in sel:
        if applyPlacementToShape(obj):
            count += 1
    App.ActiveDocument.recompute()
    print('%d objeto%s com Placement aplicado ao Shape' % (count, 's' if count > 1 else ''))
